import Part
import math
from FreeCAD import Base
#import copy


baseName = 'Lorenz'
doc = FreeCAD.newDocument(baseName)

sin30 = 0.5;
sin60 = math.sqrt(3)*0.5;
cos30 = sin60 #Makes code easier to read
cos60 = sin30
pegFit = 0.3

def union(a, b):
 result = doc.addObject("Part::Fuse",baseName)
 result.Base = a
 result.Tool = b
 return result

def difference(a, b):
 result = doc.addObject("Part::Cut",baseName)
 result.Base = a
 result.Tool = b
 return result

def mirror(a, vector, origin):
 result = doc.addObject("Part::Mirroring", baseName)
 result.Source = a
 result.Normal = vector
 result.Base = origin
 a.ViewObject.Visibility=False
 return result

def mirrorX(a):
 return mirror(a, (1,0,0), (0,0,0))

def mirrorY(a):
 return mirror(a, (0,1,0), (0,0,0))

def mirrorZ(a):
 return mirror(a, (0,0,1), (0,0,0))

def extrude(polygon, axis):
 rFace = Part.Face(polygon)
 #result = doc.addObject('Part::Feature', baseName)
 #result.Shape = rFace.extrude(axis)
 return rFace.extrude(axis)

def translate(a, vector):
 b = a.Shape.copy()
 b.translate(vector)
 result = doc.addObject('Part::Feature',baseName)
 result.Shape = b
 a.ViewObject.Visibility=False
 return result

def vc(v):
 return Base.Vector(v.x, v.y, v.z)

def strutHole(length, width, land, thickness, topCorner, rightCorner, bottomCorner, angle):
 s = math.sin(angle)
 c = math.cos(angle)
 q = topCorner.add(Base.Vector(c, s, 0).multiply(-thickness))
 y = q.y + c*(q.x - thickness)/s

 a = topCorner.sub(rightCorner)
 a.normalize()
 b = bottomCorner.sub(rightCorner)
 f = rightCorner.add(b.multiply(0.5))
 b.normalize()
 d = a.add(b)
 d.normalize()
 c = Base.Vector(0, 0, 0).sub(bottomCorner)
 c.normalize()
 e = c.sub(b)
 e.normalize()

 g = Base.Vector(b.y, -b.x, 0)

 corners = [
  Base.Vector(thickness, thickness, 0),
  Base.Vector(thickness, y, 0),
  rightCorner.add(d.multiply(thickness)),
  bottomCorner.add(e.multiply(thickness)),
  #Base.Vector(width/2+land*cos60*0.5-thickness*sin60,land*sin60*0.5+thickness*cos60,0),
  Base.Vector(thickness, thickness, 0)
  ]
 voidPart = extrude(corners, Base.Vector(0,0,length))
 b1 = vc(b)
 b1.multiply(10*thickness)
 b2 = vc(b)
 b2.multiply(-10*thickness)
 h = bottomCorner.add(b1)
 i = rightCorner.add(b2)
 g1 = vc(g)
 #print g
 #print g1
 g1.multiply(-10*thickness)
 corners2 = [
  h,
  i,
  i.add(g1),
  h.add(g1),
  h
  ]
 #print corners2
 g2 = vc(g)
 g2.multiply(2*thickness)
 cut = extrude(corners2, Base.Vector(0,0,length+10))
 cut = translate(cut, g2.add(Base.Vector(0,0,-5)))
 voidPart = difference(voidPart, cut)
 return voidPart

def strutCorners(width, land, rulerDepth, rulerThickness):
 p = [
  Base.Vector(-width/2,0,0),
  Base.Vector(-width/2-land*cos60,land*sin60,0),
  Base.Vector(-land*0.5,land*sin60+width*cos30-land*0.5,0),
  Base.Vector(-rulerThickness*0.5,land*sin60+width*cos30-land*0.5,0),
  Base.Vector(-rulerThickness*0.5,land*sin60+width*cos30-rulerDepth,0),
  Base.Vector(rulerThickness*0.5,land*sin60+width*cos30-rulerDepth,0),
  Base.Vector(rulerThickness*0.5,land*sin60+width*cos30-land*0.5,0),
  Base.Vector(land*0.5,land*sin60+width*cos30-land*0.5,0),
  Base.Vector(width/2+land*cos60,land*sin60,0),
  Base.Vector(width/2,0,0),
  Base.Vector(-width/2,0,0)
  ]
 return Part.makePolygon(p)

def strut(length, width, land, rulerDepth, rulerThickness, thickness, indent, tubeRadius):
 corners = strutCorners(width, land, rulerDepth, rulerThickness)
 ex = Part.hide(extrude(corners, Base.Vector(0,0,length)))
 #mybox1 = Part.makeBox(4,4,4,Base.Vector(-2,-2,-2))
 cl = Part.hide(Part.makeCylinder(tubeRadius,length+10))
 #angle = math.atan((corners[8].x - corners[7].x)/(corners[7].y - corners[8].y))

 #result = strutHole(length+10, width, land, 2*thickness, corners[7], corners[8], corners[9], angle)
 #hole = translate(hole, Base.Vector(0,0,-5))
 result = Part.show(ex.cut(cl))#difference(ex, cl)
 #Part.show(result)

# hole = mirrorX(hole)
#result = difference(result, hole)

# hole = strutHole(indent+1, width, land, thickness, corners[7], corners[8], corners[9], angle)
# hole = translate(hole, Base.Vector(0,0,-1))
# result = difference(result, hole)

# hole = mirrorX(hole)
# result = difference(result, hole)

# hole = translate(hole, Base.Vector(0,0,length-indent))
# result = difference(result, hole)

# hole = mirrorX(hole)
# result = difference(result, hole)

 return result

def peg(width, land, rulerDepth, rulerThickness, thickness, indent):
 corners = strutCorners(width, land, rulerDepth, rulerThickness)
 angle = math.atan((corners[8].x - corners[7].x)/(corners[7].y - corners[8].y))

 hole = strutHole(indent+10, width, land, 2*thickness, corners[7], corners[8], corners[9], angle)
 hole = translate(hole, Base.Vector(width,0,-5))

 result = strutHole(indent, width, land, thickness, corners[7], corners[8], corners[9], angle)
 result = translate(result, Base.Vector(width,0,0))
 result = difference(result, hole)
 return result

length=100
width=45
land=6
rulerDepth=26.36
rulerThickness=0.63
thickness=2.5
indent=10
tubeRadius=2
st = strut(length, width, land, rulerDepth, rulerThickness, thickness, indent, tubeRadius)
#pg = peg(width, land, rulerDepth, rulerThickness, thickness, 2*indent-pegFit)
#st = strut(100.0, 30, 4.0, 15, 0.63, 2.5, 10)
Part.show(st)
Gui.SendMsgToActiveView("ViewFit")
doc.recompute()
